module openconfig-bgp-gue {

  yang-version "1";

  // namespace
  namespace "http://openconfig.net/yang/bgp-triggered-gue";

  prefix "oc-bgp-gue";

  import openconfig-extensions { prefix oc-ext; }
  import openconfig-inet-types { prefix oc-inet; }

  // meta
  organization "OpenConfig working group";

  contact
    "OpenConfig working group
    www.openconfig.net";

  description
    "This module defines configuration and operational state
    data for BGP-triggered GUE Policies.

    NOTE: This is a DRAFT for demonstrating this feature that only contains a
    subset of the complete configuration of this feature. It WILL be different
    from the final YANG to be checked into github.com/openconfig/public as more
    configuration knobs are applied, and this feature is viewed in context of
    other features.";

  oc-ext:openconfig-version "0.1.0";

  revision "2022-11-10" {
    description
      "Initial revision";
    reference "0.1.0";
  }

  // OpenConfig specific extensions for module metadata.
  oc-ext:catalog-organization "openconfig";
  oc-ext:origin "openconfig";

  // grouping statements

  grouping bgp-gue-ipv4-global-policy-config {
    description
      "Config data for IPv4 BGP-triggered GUE global policy";

    leaf prefix {
      type oc-inet:ipv4-prefix;
      description
        "Prefix containing BGP path's next-hop attribute of NLRI to which GUE
        global policy applies.

        In case of overlapping prefixes, the global policy with the
        longest-matching prefix will apply.";
    }

    leaf dst-port-ipv4 {
      type oc-inet:port-number;
      description
        "Destination port of UDP encap for an IPv4 payload.";
    }

    leaf dst-port-ipv6 {
      type oc-inet:port-number;
      description
        "Destination port of UDP encap for an IPv6 payload.";
    }

    leaf src-ip {
      type oc-inet:ipv4-address;
      description
        "Source IP address of IPv4 encap.";
    }
  }

  grouping bgp-gue-ipv6-global-policy-config {
    description
      "Config data for IPv6 BGP-triggered GUE global policy";

    leaf prefix {
      type oc-inet:ipv6-prefix;
      description
        "Prefix containing BGP path's next-hop attribute of NLRI to which GUE
        global policy applies.

        In case of overlapping prefixes, the global policy with the
        longest-matching prefix will apply.

        Any prefix coverage of IPv4-mapped IPv6 addresses will be ignored,
        since the IPv4 global policy must be used for IPv4 next-hop
        addresses.";
    }

    leaf dst-port-ipv6 {
      type oc-inet:port-number;
      description
        "Destination port of UDP encap for an IPv6 payload.";
    }

    leaf src-ip {
      type oc-inet:ipv6-address;
      description
        "Source IP address of IPv6 encap.";
    }
  }

  grouping bgp-gue-top {
    description
      "Top level grouping for BGP-triggered GUE.";

    container bgp-gue-ipv4-policies {
      description
        "Container for List of BGP-triggered IPv4 GUE policies.";

      list bgp-gue-ipv4-global-policy {
        key "prefix";
        description
          "List of BGP-triggered IPv4 GUE policies.";

        leaf prefix {
          type leafref {
            path "../config/prefix";
          }
          description
            "Prefix containing BGP path's next-hop attribute of NLRI to which
            the GUE global policy applies.

            In case of overlapping prefixes, the global policy with the
            longest-matching prefix will apply.";
        }

        container config {
          description
            "Config data for BGP-triggered GUE global policy.";

          uses bgp-gue-ipv4-global-policy-config;
        }

        container state {
          config false;
          description
            "State data for BGP-triggered GUE global policy.";

          uses bgp-gue-ipv4-global-policy-config;
        }
      }
    }

    container bgp-gue-ipv6-policies {
      description
        "Container for List of BGP-triggered IPv6 GUE policies.";

      list bgp-gue-ipv6-global-policy {
        key "prefix";
        description
          "List of BGP-triggered IPv6 GUE policies.";

        leaf prefix {
          type leafref {
            path "../config/prefix";
          }
          description
            "Prefix containing BGP path's next-hop attribute of NLRI to which
            the GUE global policy applies.

            In case of overlapping prefixes, the global policy with the
            longest-matching prefix will apply.";
        }

        container config {
          description
            "Config data for BGP-triggered GUE global policy.";

          uses bgp-gue-ipv6-global-policy-config;
        }

        container state {
          config false;
          description
            "State data for BGP-triggered GUE global policy.";

          uses bgp-gue-ipv6-global-policy-config;
        }
      }
    }
  }

  // data definition statements
  uses bgp-gue-top;

  // augment statements
}
